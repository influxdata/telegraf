module openconfig-macsec-types {
  yang-version "1";
  namespace "http://openconfig.net/yang/macsec/types";
  prefix "oc-macsect";

  import openconfig-extensions { prefix oc-ext; }

  organization "OpenConfig working group";
  contact
    "OpenConfig working group
    www.openconfig.net";
  description
    "This module defines types related to the MACsec configuration
    and operational state model.";

  oc-ext:openconfig-version "0.1.0";
  oc-ext:regexp-posix;
  oc-ext:catalog-organization "openconfig";
  oc-ext:origin "openconfig";

  revision 2019-07-01 {
    description
      "Initial public revision";
    reference
      "0.1.0";
  }

  typedef macsec-cipher-suite {
    type enumeration {
      enum GCM_AES_128 { description "GCM-AES-128 Cipher Suite"; }
      enum GCM_AES_256 { description "GCM-AES-256 Cipher Suite"; }
      enum GCM_AES_XPN_128 { description "GCM-AES-XPN-128 Cipher Suite"; }
      enum GCM_AES_XPN_256 { description "GCM-AES-XPN-256 Cipher Suite"; }
    }
    description
      "Set Cipher suite(s) for SAK derivation";
  }

  typedef confidentiality-offset {
    type enumeration {
      enum "0_BYTES" { description "No octets are sent unencrypted"; }
      enum "30_BYTES" { description "30 octects are sent unencrypted"; }
      enum "50_BYTES" { description "50 octects are sent unencrypted"; }
    }
    description
      "The confidentiality offset specifies a number of octets in an Ethernet
       frame that are sent in unencrypted plain-text";
  }

}

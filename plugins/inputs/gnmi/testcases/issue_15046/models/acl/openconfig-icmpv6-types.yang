module openconfig-icmpv6-types {

  yang-version "1";
  namespace "http://openconfig.net/yang/openconfig-icmpv6-types";

  prefix "oc-icmpv6-types";

  import openconfig-extensions { prefix oc-ext; }

  organization "OpenConfig working group";

  contact
    "OpenConfig working group
    www.openconfig.net";

  description
    "OpenConfig module defining the types and coresponding subcodes for
    ICMPv6.";

  oc-ext:openconfig-version "0.1.1";

  revision "2023-05-02" {
    description
      "Fix module prefix.";
    reference "0.1.1";
  }

  revision "2023-01-26" {
    description
      "Initial revision of ICMPv6 types module.";
    reference "0.1.0";
  }

  identity TYPE {
    description
      "Base identity for ICMPv6 codes";
  }

  identity CODE {
    description
      "Base identity for ICMPv6 subcodes.";
  }

  identity DESTINATION_UNREACHABLE {
    base TYPE;
    description
      "Type 1: Destination unreachable.";
    reference
      "RFC4443: Internet Control Message Protocol (ICMPv6)
      for the Internet Protocol Version 6 (IPv6) Specification";
  }

  identity PACKET_TOO_BIG {
    base TYPE;
    description
      "Type 2: Packet too big.";
    reference
      "RFC4443: Internet Control Message Protocol (ICMPv6)
      for the Internet Protocol Version 6 (IPv6) Specification";
  }

  identity TIME_EXCEEDED {
    base TYPE;
    description
      "Type 3: Time exceeded.";
    reference
      "RFC4443: Internet Control Message Protocol (ICMPv6)
      for the Internet Protocol Version 6 (IPv6) Specification";
  }

  identity PARAMETER_PROBLEM {
    base TYPE;
    description
      "Type 4: Parameter problem.";
    reference
      "RFC4443: Internet Control Message Protocol (ICMPv6)
      for the Internet Protocol Version 6 (IPv6) Specification";
  }

  identity ECHO_REQUEST {
    base TYPE;
    description
      "Type 128: Echo request.";
    reference
      "RFC4443: Internet Control Message Protocol (ICMPv6)
      for the Internet Protocol Version 6 (IPv6) Specification";
  }

  identity ECHO_REPLY {
    base TYPE;
    description
      "Type 129: Echo reply";
    reference
      "RFC4443: Internet Control Message Protocol (ICMPv6)
      for the Internet Protocol Version 6 (IPv6) Specification";
  }

  identity MULTICAST_LISTENER_QUERY {
    base TYPE;
    description
      "Type 130: Multicast listener query";
    reference
      "RFC2710: Multicast Listener Discovery (MLD) for IPv6";
  }

  identity MULTICAST_LISTENER_REPORT {
    base TYPE;
    description
      "Type 131: Multicast listener report";
    reference
      "RFC2710: Multicast Listener Discovery (MLD) for IPv6";
  }

  identity MULTICAST_LISTENER_DONE {
    base TYPE;
    description
      "Type 132: Multicast listener done";
    reference
      "RFC2710: Multicast Listener Discovery (MLD) for IPv6";
  }

  identity ROUTER_SOLICITATION {
    base TYPE;
    description
      "Type 133: IPv6 router soliciation.";
    reference
      "RFC4861: Neighbor Discovery for IP version 6 (IPv6)";
  }

  identity ROUTER_ADVERTISEMENT {
    base TYPE;
    description
      "Type 134: IPv6 router advertisement.";
    reference
      "RFC4861: Neighbor Discovery for IP version 6 (IPv6)";
  }

  identity NEIGHBOR_SOLICITATION {
    base TYPE;
    description
      "Type 135: IPv6 neighbor solicitation.";
    reference
      "RFC4861: Neighbor Discovery for IP version 6 (IPv6)";
  }

  identity NEIGHBOR_ADVERTISEMENT {
    base TYPE;
    description
      "Type 136: IPv6 neighbor advertisement.";
    reference
      "RFC4861: Neighbor Discovery for IP version 6 (IPv6)";
  }

  identity REDIRECT {
    base TYPE;
    description
      "Type 137: IPv6 ICMP redirect message.";
    reference
      "RFC4861: Neighbor Discovery for IP version 6 (IPv6)";
  }

  identity RENUNBERING {
    base TYPE;
    description
      "Type 138: Router renumbering.";
    reference
      "RFC2894: Router Renumbering for IPv6";
  }

  identity NODE_INFORMATION_QUERY {
    base TYPE;
    description
      "Type 139: ICMP Node Information Query.";
    reference
      "RFC4620: IPv6 Node Information Queries";
  }
  identity NODE_INFORMATION_RESPONSE {
    base TYPE;
    description
      "Type 140: ICMP Node Information Response.";
    reference
      "RFC4620: IPv6 Node Information Queries";
  }

  identity INVERSE_NEIGHBOR_SOLICITATION {
    base TYPE;
    description
      "Type 141: Inverse Neighbor Discovery Solicitation Message.";
    reference "RFC3122: Extensions to IPv6 Neighbor Discovery for
              Inverse Discovery Specification";
  }

  identity INVERSE_NEIGHBOR_ADVERTISEMENT {
    base TYPE;
    description
      "Type 142: Inverse Neighbor Discovery Advertisement Message.";
    reference "RFC3122: Extensions to IPv6 Neighbor Discovery for
              Inverse Discovery Specification";
  }

  identity VERSION2_MULTICAST_LISTENER {
    base TYPE;
    description
      "Type 143: Version 2 Multicast Listener Report";
    reference
      "RFC3810: Multicast Listener Discovery Version 2 (MLDv2) for IPv6";
  }

  identity HOME_AGENT_ADDRESS_DISCOVERY_REQUEST {
    base TYPE;
    description
      "Type 144: Home Agent Address Discovery Request Message.";
    reference "RFC6275: Mobility Support in IPv6";

  }

  identity HOME_AGENT_ADDRESS_DISCOVERY_REPLY {
    base TYPE;
    description
      "Type 145: Home Agent Address Discovery Reply Message.";
    reference "RFC6275: Mobility Support in IPv6";

  }

  identity MOBILE_PREFIX_SOLICITATION {
    base TYPE;
    description
      "Type 147: Mobile Prefix Solicitation.";
    reference "RFC6275: Mobility Support in IPv6";
  }

  identity MOBILE_PREFIX_ADVERTISEMENT {
    base TYPE;
    description
      "Type 147: Mobile Prefix Advertisement.";
    reference "RFC6275: Mobility Support in IPv6";
  }

  identity CERTIFICATION_PATH_SOLICITATION {
    base TYPE;
    description
      "Type 148: Certification Path Soliciation Message.";
    reference "RFC3971: SEcure Neighbor Discovery (SEND)";
  }

  identity CERTIFICATION_PATH_ADVERTISEMENT {
    base TYPE;
    description
      "Type 149: Certification Path Advertisement Message.";
    reference "RFC3971: SEcure Neighbor Discovery (SEND)";
  }

  identity MULTICAST_ROUTER_ADVERTISEMENT {
    base TYPE;
    description
      "Type 151: Multicast Router Advertisement.";
    reference "RFC4286: Multicast Router Discovery";
  }

  identity MULTICAST_ROUTER_SOLICITATION {
    base TYPE;
    description
      "Type 152: Multicast Router Solicitation.";
    reference "RFC4286: Multicast Router Discovery";
  }

  identity MULTICAST_ROUTER_TERMINATION {
    base TYPE;
    description
      "Type 153: Multicast Router Termination.";
    reference "RFC4286: Multicast Router Discovery";
  }

  identity FMIPV6 {
    base TYPE;
    description
      "Type 154: Fast handover mode for IPv6.";
    reference
      "RFC5568: Mobile IPv6 Fast Handovers";
  }

  identity RPL_CONTROL {
    base TYPE;
    description
      "Type 155: RPL Control Message.";
    reference
      "RFC6550: RPL: IPv6 Routing Protocol for Low-Power and Lossy Networks";
  }

  identity ILNPV6_LOCATOR_UPDATE {
    base TYPE;
    description
      "Type 156: ILNPv6 Locator Update Message.";
    reference
      "RFC6743: ICMP Locator Update Message for
       the Identifier-Locator Network Protocol for IPv6 (ILNPv6)";
  }

  identity DUPLICATE_ADDRESS_REQUEST {
    base TYPE;
    description
      "Type 157: Duplicate address request.";
    reference
      "RFC6775: Neighbor Discovery Optimization for IPv6 over Low-Power Wireless
                Personal Area Networks (6LoWPANs)";
  }

  identity DUPLICATE_ADDRESS_CONFIRMATION {
    base TYPE;
    description
      "Type 158: Duplicate address confirmation.";
    reference
      "RFC6775: Neighbor Discovery Optimization for IPv6 over Low-Power Wireless
                Personal Area Networks (6LoWPANs)";
  }

  identity MPL_CONTROL {
    base TYPE;
    description
      "Type 159: MPL Control Message.";
    reference
      "RFC7731: Multicast Protocol for Low-Power and Lossy Networks (MPL)";
  }

  identity EXT_ECHO_REQUEST {
    base TYPE;
    description
      "Type 160: Extended echo request.";
    reference
      "RFC8335: PROBE: A Utility for Probing Interfaces";
  }

  identity EXT_ECHO_REPLY {
    base TYPE;
    description
      "Type 161: Extended echo reply.";
    reference
      "RFC8335: PROBE: A Utility for Probing Interfaces";
  }

  identity DST_UNREACHABLE_CODE {
    base CODE;
    description
      "ICMPv6 destination unreachable subcodes.";
  }
  identity DST_UNREACHABLE_NO_ROUTE_TO_DST {
    base DST_UNREACHABLE_CODE;
    description
      "Code 0: No route to destination.";
    reference "RFC4443: Internet Control Message Protocol (ICMPv6)
          for the Internet Protocol Version 6 (IPv6) Specification";
  }
  identity DST_UNREACHABLE_DST_ADMIN_PROHIBITED {
    base DST_UNREACHABLE_CODE;
    description
      "Code 1: Communication with destination adminstratively prohibited.";
    reference "RFC4443: Internet Control Message Protocol (ICMPv6)
              for the Internet Protocol Version 6 (IPv6) Specification";
  }

  identity DST_UNREACHABLE_BEYOND_SCOPE_OF_SRC {
    base DST_UNREACHABLE_CODE;
    description
      "Code 2: Beyond scope of source address.";
    reference "RFC4443: Internet Control Message Protocol (ICMPv6)
              for the Internet Protocol Version 6 (IPv6) Specification";
  }

  identity DST_UNREACHABLE_ADDR {
    base DST_UNREACHABLE_CODE;
    description
      "Code 3: Address unreachable.";
    reference "RFC4443: Internet Control Message Protocol (ICMPv6)
              for the Internet Protocol Version 6 (IPv6) Specification";
  }

  identity DST_UNREACHABLE_PORT {
    base DST_UNREACHABLE_CODE;
    description
      "Code 4: Port unreachable.";
    reference "RFC4443: Internet Control Message Protocol (ICMPv6)
              for the Internet Protocol Version 6 (IPv6) Specification";
  }

  identity DST_UNREACHABLE_SRC_ADDR_FAILED_POLICY {
    base DST_UNREACHABLE_CODE;
    description
      "Code 5: Source address failed ingress/egress policy.";
    reference "RFC4443: Internet Control Message Protocol (ICMPv6)
              for the Internet Protocol Version 6 (IPv6) Specification";
  }

  identity DST_UNREACHABLE_REJECT_ROUTE_TO_DST {
    base DST_UNREACHABLE_CODE;
    description
      "Code 6: Reject route to destination.";
    reference "RFC4443: Internet Control Message Protocol (ICMPv6)
              for the Internet Protocol Version 6 (IPv6) Specification";
  }

  identity DST_UNREACHABLE_ERR_IN_SRC_ROUTING_HDR {
    base DST_UNREACHABLE_CODE;
    description
      "Code 7: Error in Source Routing Header.";
    reference "RFC8554: An IPv6 Routing Header for Source Routes with
              the Routing Protocol for Low-Power and Lossy Networks (RPL)";
  }

  identity DST_UNREACHABLE_HDRS_TOO_LONG {
    base DST_UNREACHABLE_CODE;
    description
      "Type 8: Headers too long";
    reference "RFC8883: ICMPv6 Errors for Discarding Packets Due to
              Processing Limits";
  }

  identity PACKET_TOO_BIG_CODE {
    base CODE;
    description
      "Subcodes for the ICMPv6 Packet Too Big type.";
  }

  identity PACKET_TOO_BIG_NO_CODE {
    base PACKET_TOO_BIG_CODE;
    description
      "No code, value 0.";
    reference "RFC4443: Internet Control Message Protocol (ICMPv6)
              for the Internet Protocol Version 6 (IPv6) Specification";
  }

  identity TIME_EXCEEDED_CODE {
    base CODE;
    description
      "Subcodes for the Time Exceeded ICMPv6 type.";
  }

  identity TIME_EXCEEDED_HOP_LIMIT {
    base TIME_EXCEEDED_CODE;
    description
      "Code 0: Hop limit exceeded in transit.";
    reference "RFC4443: Internet Control Message Protocol (ICMPv6)
              for the Internet Protocol Version 6 (IPv6) Specification";
  }
  identity TIME_EXCEEDED_FRAGMENT_REASSEMBLY {
    base TIME_EXCEEDED_CODE;
    description
      "Code 1: Fragment reassembly time exceeded.";
    reference "RFC4443: Internet Control Message Protocol (ICMPv6)
              for the Internet Protocol Version 6 (IPv6) Specification";
  }

  identity PARAM_PROBLEM_CODE {
    base CODE;
    description
      "Subcodes for the Parameter Problem ICMPv6 type.";
  }

  identity PARAM_PROBLEM_ERR_HDR_FIELD {
    base PARAM_PROBLEM_CODE;
    description
      "Erroneous header field encountered.";
    reference "RFC4443: Internet Control Message Protocol (ICMPv6)
              for the Internet Protocol Version 6 (IPv6) Specification";
  }

  identity PARAM_PROBLEM_UNRECOGNIZED_NET_HDR_TYPE {
    base PARAM_PROBLEM_CODE;
    description
      "Unrecognized Next Header type encountered.";
    reference "RFC4443: Internet Control Message Protocol (ICMPv6)
              for the Internet Protocol Version 6 (IPv6) Specification";
  }

  identity PARAM_PROBLEM_UNRECOGNIZED_IPV6_OPT {
    base PARAM_PROBLEM_CODE;
    description
      "Unrecognized IPv6 option encountered.";
    reference "RFC4443: Internet Control Message Protocol (ICMPv6)
              for the Internet Protocol Version 6 (IPv6) Specification";
  }

  identity PARAM_PROBLEM_INCOMPLETE_HDR_CHAIN {
    base PARAM_PROBLEM_CODE;
    description
      "IPv6 First Fragment has incomplete IPv6 Header Chain.";
    reference
      "RFC7112: Implications of Oversized IPv6 Header Chains";
  }

  identity PARAM_PROBLEM_SR_UPPER_HDR_ERR {
    base PARAM_PROBLEM_CODE;
    description
      "SR Upper-layer Header Error";
    reference
      "RFC8754: IPv6 Segment Routing Header (SRH)";
  }

  identity PARAM_PROBLEM_UNRECOGNIZED_NEXT_HDR_TYPE {
    base PARAM_PROBLEM_CODE;
    description
      "Unrecognized Next Header type encountered by intermediate node";
    reference
      "RFC8883: ICMPv6 Errors for Discarding Packets Due to Processing Limits";
  }

  identity PARAM_PROBLEM_EXT_HDR_TOO_BIG {
    base PARAM_PROBLEM_CODE;
    description
      "Extension header too big.";
    reference
      "RFC8883: ICMPv6 Errors for Discarding Packets Due to Processing Limits";
  }

  identity PARAM_PROBLEM_EXT_HDR_CHAIN_TOO_LONG {
    base PARAM_PROBLEM_CODE;
    description
      "Extension header chain too long.";
    reference
      "RFC8883: ICMPv6 Errors for Discarding Packets Due to Processing Limits";
  }

  identity PARAM_PROBLEM_TOO_MANY_EXT_HDRS {
    base PARAM_PROBLEM_CODE;
    description
      "Too many extension headers.";
    reference
      "RFC8883: ICMPv6 Errors for Discarding Packets Due to Processing Limits";
  }

  identity PARAM_PROBLEM_TOO_MANY_OPTS {
    base PARAM_PROBLEM_CODE;
    description
      "Too many options in extension header.";
    reference
      "RFC8883: ICMPv6 Errors for Discarding Packets Due to Processing Limits";
  }

  identity PARAM_PROBLEM_OPT_TOO_BIG {
    base PARAM_PROBLEM_CODE;
    description
      "Option too big.";
    reference
      "RFC8883: ICMPv6 Errors for Discarding Packets Due to Processing Limits";
  }

  identity ECHO_REQUEST_CODE {
    base CODE;
    description
      "Subcodes for the ICMPv6 echo request type.";
  }

  identity ECHO_REQUEST_NO_CODE {
    base ECHO_REQUEST_CODE;
    description
      "No code.";
    reference "RFC4443: Internet Control Message Protocol (ICMPv6)
              for the Internet Protocol Version 6 (IPv6) Specification";
  }

  identity ECHO_REPLY_CODE {
    base CODE;
    description
      "Subcodes for the ICMPv6 echo reply subcode.";
  }

  identity ECHO_REPLY_NO_CODE {
    base ECHO_REPLY_CODE;
    description
      "No code.";
    reference "RFC4443: Internet Control Message Protocol (ICMPv6)
              for the Internet Protocol Version 6 (IPv6) Specification";
  }

  identity MULTICAST_LISTENER_QUERY_CODE {
    base CODE;
    description
      "Subcodes for the multicast listener query ICMPv6 type.";
  }

  identity MULTICAST_LISTENER_QUERY_NO_CODE {
    base MULTICAST_LISTENER_QUERY_CODE;
    description
      "No code.";
    reference
      "RFC2710: Multicast Listener Discovery (MLD) for IPv6";
  }

  identity MULTICAST_LISTENER_REPORT_CODE {
    base CODE;
    description
      "Subcodes for the multicast listener report ICMPv6 type.";
  }

  identity MULTICAST_LISTENER_REPORT_NO_CODE {
    base MULTICAST_LISTENER_REPORT_CODE;
    description
      "No code.";
    reference
      "RFC2710: Multicast Listener Discovery (MLD) for IPv6";
  }

  identity MULTICAST_LISTENER_DONE_CODE {
    base CODE;
    description
      "Subcodes for the multicast listener done ICMPv6 type.";
  }

  identity MULTICAST_LISTENER_DONE_NO_CODE {
    base MULTICAST_LISTENER_DONE_CODE;
    description
      "No code.";
    reference
      "RFC2710: Multicast Listener Discovery (MLD) for IPv6";
  }

  identity ROUTER_SOLICITATION_CODE {
    base CODE;
    description
      "Subcodes for the router solicitation ICMPv6 type.";
  }
  identity ROUTER_SOLICITATION_NO_CODE {
    base ROUTER_SOLICITATION_CODE;
    description
      "No code.";
    reference
      "RFC4861: Neighbor Discovery for IP version 6 (IPv6)";
  }

  identity ROUTER_ADVERTISEMENT_CODE {
    base CODE;
    description
      "Subcodes for the router advertisement ICMPv6 type.";
  }

  identity ROUTER_ADVERTISEMENT_NO_CODE {
    base ROUTER_ADVERTISEMENT_CODE;
    description
      "No code.";
    reference
      "RFC4861: Neighbor Discovery for IP version 6 (IPv6)";
  }

  identity NEIGHBOR_SOLICITATION_CODE {
    base CODE;
    description
      "Subcodes for the router solicitation ICMPv6 type.";
  }

  identity NEIGHBOR_SOLICITATION_NO_CODE {
    base NEIGHBOR_SOLICITATION_CODE;
    description
      "No code.";
    reference
      "RFC4861: Neighbor Discovery for IP version 6 (IPv6)";
  }

  identity NEIGHBOR_ADVERTISEMENT_CODE {
    base CODE;
    description
      "Subcodes for the neighbor advertisement ICMPv6 type.";
  }

  identity NEIGHBOR_ADVERTISEMENT_NO_CODE {
    base NEIGHBOR_ADVERTISEMENT_CODE;
    description
      "No code.";
    reference
      "RFC4861: Neighbor Discovery for IP version 6 (IPv6)";
  }

  identity REDIRECT_CODE {
    base CODE;
    description
      "Subcodes for the redirect ICMPv6 type.";
  }

  identity REDIRECT_NO_CODE {
    base REDIRECT_CODE;
    description
      "No code.";
    reference
      "RFC4861: Neighbor Discovery for IP version 6 (IPv6)";
  }

  identity RENUMBERING_CODE {
    base CODE;
    description
      "Subcodes for the redirect ICMPv6 type for renumbering.";
  }

  identity RENUMBERING_COMMAND {
    base RENUMBERING_CODE;
    description
      "Router renumbering command.";
    reference
      "RFC2894: Router Renumbering for IPv6";
  }

  identity RENUNBERING_RESULT {
    base RENUMBERING_CODE;
    description
      "Router renumbering result.";
    reference
      "RFC2894: Router Renumbering for IPv6";
  }

  identity RENUNBERING_SEQ_NUM_RESET {
    base RENUMBERING_CODE;
    description
      "Router renumbering sequence number reset.";
    reference
      "RFC2894: Router Renumbering for IPv6";
  }

  identity NODE_INFORMATION_QUERY_CODE {
    base CODE;
    description
      "Subcodes for the node information query ICMPv6 type.";
  }

  identity NODE_INFORMATION_QUERY_IPV6_ADDR {
    base NODE_INFORMATION_QUERY_CODE;
    description
      "The data field contains an IPv6 address which is the subject of the
      query.";
    reference
      "RFC4620: IPv6 Node Information Queries";
  }

  identity NODE_INFORMATION_QUERY_NAME {
    base NODE_INFORMATION_QUERY_CODE;
    description
      "The data field contains a name which is the subject of the
      query.";
    reference
      "RFC4620: IPv6 Node Information Queries";
  }

  identity NODE_INFORMATION_QUERY_IPV4_ADDR {
    base NODE_INFORMATION_QUERY_CODE;
    description
      "The data field contains an IPv4 address which is the subject of the
      query.";
    reference
      "RFC4620: IPv6 Node Information Queries";
  }

  identity NDDE_INFORMATION_RESPONSE_CODE {
    base CODE;
    description
      "Subcodes for the node information response ICMPv6 type.";
  }

  identity NODE_INFORMATION_RESPONSE_SUCCESS {
    base NDDE_INFORMATION_RESPONSE_CODE;
    description
      "A successful reply.";
    reference
      "RFC4620: IPv6 Node Information Queries";
  }

  identity NODE_INFORMATION_RESPONSE_REFUSED {
    base NDDE_INFORMATION_RESPONSE_CODE;
    description
      "The responder refuses to supply the answer.";
    reference
      "RFC4620: IPv6 Node Information Queries";
  }

  identity NODE_INFORMATION_RESPONSE_UNKNOWN {
    base NDDE_INFORMATION_RESPONSE_CODE;
    description
      "The query type is unknown to the responder.";
    reference
      "RFC4620: IPv6 Node Information Queries";
  }

  identity INVERSE_NEIGHBOR_ADVERTISEMENT_CODE {
    base CODE;
    description
      "Subcodes for the Inverse Neighbor Discovery ICMPv6 type.";
  }

  identity INVERSE_NEIGHBOR_ADVERTISEMENT_NO_CODE {
    base INVERSE_NEIGHBOR_ADVERTISEMENT_CODE;
    description
      "No code.";
    reference
      "RFC3122: Extensions to IPv6 Neighbor Discovery for Inverse Discovery
      Specification";
  }

  identity INVERSE_NEIGHBOR_SOLICITATION_CODE {
    base CODE;
    description
      "Subcode for the inverse neighbor solicitation ICMP6 type.";
  }

  identity INVERSE_NEIGHBOR_SOLICITATION_NO_CODE {
    base INVERSE_NEIGHBOR_SOLICITATION_CODE;
    description
      "No code.";
    reference
      "RFC3122: Extensions to IPv6 Neighbor Discovery for Inverse Discovery
      Specification";
  }

  identity HOME_AGENT_ADDRESS_DISCOVERY_REQUEST_CODE {
    base CODE;
    description
      "Subcodes for the Home Agent Address Discovery Request ICMPv6 type.";
  }

  identity HOME_AGENT_ADDRESS_DISCOVERY_REQUEST_NO_CODE {
    base HOME_AGENT_ADDRESS_DISCOVERY_REQUEST_CODE;
    description
      "No code.";
    reference "RFC3775: Mobility Support in IPv6";
  }

  identity HOME_AGENT_ADDRESS_DISCOVERY_REPLY_CODE {
    base CODE;
    description
      "Subcodes for the Home Agent Address Discovery Reply ICMPv6 type.";
  }

  identity HOME_AGENT_ADDRESS_DISCOVERY_REPLY_NO_CODE {
    base HOME_AGENT_ADDRESS_DISCOVERY_REPLY_CODE;
    description
      "No code.";
    reference "RFC3775: Mobility Support in IPv6";
  }

  identity MOBILE_PREFIX_SOLICITATION_CODE {
    base CODE;
    description
      "Subcodes for the Mobile Prefix Solicitation ICMPv6 type.";
  }

  identity MOBILE_PREFIX_SOLICITATION_NO_CODE {
    base MOBILE_PREFIX_SOLICITATION_CODE;
    description
      "No code.";
    reference "RFC3775: Mobility Support in IPv6";
  }

  identity MOBILE_PREFIX_ADVERTISEMENT_CODE {
    base CODE;
    description
      "Subcodes for the Mobile Prefix Advertisement ICMPv6 type.";
  }

  identity MOBILE_PREFIX_ADVERTISEMENT_NO_CODE {
    base MOBILE_PREFIX_ADVERTISEMENT_CODE;
    description
      "No code.";
    reference "RFC3775: Mobility Support in IPv6";
  }

  identity DUPLICATE_ADDRESS_REQUEST_CODE {
    base CODE;
    description
      "Subcodes for the Duplicate Address Request ICMPv6 type.";
  }

  identity DUPLICATE_ADDRESS_REQUEST_DAR {
    base DUPLICATE_ADDRESS_REQUEST_CODE;
    description
      "DAR message";
    reference "RFC6775: Neighbor Discovery Optimization for IPv6 over
              Low-Power Wireless Personal Area Networks (6LoWPANs)";
  }

  identity DUPLICATE_ADDRESS_REQUEST_EDAR_ROVR64 {
    base DUPLICATE_ADDRESS_REQUEST_CODE;
    description
      "EDAR message with 64-bit ROVR field.";
    reference "RFC6775: Neighbor Discovery Optimization for IPv6 over
              Low-Power Wireless Personal Area Networks (6LoWPANs)";
  }

  identity DUPLICATE_ADDRESS_REQUEST_EDAR_ROVR128 {
    base DUPLICATE_ADDRESS_REQUEST_CODE;
    description
      "EDAR message with 128-bit ROVR field.";
    reference "RFC6775: Neighbor Discovery Optimization for IPv6 over
              Low-Power Wireless Personal Area Networks (6LoWPANs)";
  }

  identity DUPLICATE_ADDRESS_REQUEST_EDAR_ROVR192 {
    base DUPLICATE_ADDRESS_REQUEST_CODE;
    description
      "EDAR message with 192-bit ROVR field.";
    reference "RFC6775: Neighbor Discovery Optimization for IPv6 over
              Low-Power Wireless Personal Area Networks (6LoWPANs)";
  }

  identity DUPLICATE_ADDRESS_REQUEST_EDAR_ROVR256 {
    base DUPLICATE_ADDRESS_REQUEST_CODE;
    description
      "EDAR message with 256-bit ROVR field.";
    reference "RFC6775: Neighbor Discovery Optimization for IPv6 over
              Low-Power Wireless Personal Area Networks (6LoWPANs)";
  }

  identity DUPLICATE_ADDRESS_REPLY_CODE {
    base CODE;
    description
      "Subcodes for the Duplicate Address Confirmation Code ICMPv6 type.";
  }

  identity DUPLICATE_ADDRESS_REPLY_DAC {
    base DUPLICATE_ADDRESS_REPLY_CODE;
    description
      "DAC message";
    reference "RFC6775: Neighbor Discovery Optimization for IPv6 over
              Low-Power Wireless Personal Area Networks (6LoWPANs)";
  }
  identity DUPLICATE_ADDRESS_REPLY_EDAC_ROVR64 {
    base DUPLICATE_ADDRESS_REPLY_CODE;
    description
      "EDAC message with 64-bit ROVR field.";
    reference "RFC6775: Neighbor Discovery Optimization for IPv6 over
              Low-Power Wireless Personal Area Networks (6LoWPANs)";
  }

  identity DUPLICATE_ADDRESS_REPLY_EDAC_ROVR128 {
    base DUPLICATE_ADDRESS_REPLY_CODE;
    description
      "EDAC message with 128-bit ROVR field.";
    reference "RFC6775: Neighbor Discovery Optimization for IPv6 over
              Low-Power Wireless Personal Area Networks (6LoWPANs)";
  }

  identity DUPLICATE_ADDRESS_REPLY_EDAC_ROVR192 {
    base DUPLICATE_ADDRESS_REPLY_CODE;
    description
      "EDAC message with 192-bit ROVR field.";
    reference "RFC6775: Neighbor Discovery Optimization for IPv6 over
              Low-Power Wireless Personal Area Networks (6LoWPANs)";
  }

  identity DUPLICATE_ADDRESS_REPLY_EDAC_ROVR256 {
    base DUPLICATE_ADDRESS_REPLY_CODE;
    description
      "EDAC message with 256-bit ROVR field.";
    reference "RFC6775: Neighbor Discovery Optimization for IPv6 over
              Low-Power Wireless Personal Area Networks (6LoWPANs)";
  }

  identity EXT_ECHO_REQUEST_CODE {
    base CODE;
    description
      "Subcodes for the extended echo request ICMPv6 type.";
  }

  identity EXT_ECHO_REQUEST_NO_ERROR {
    base EXT_ECHO_REQUEST_CODE;
    description
      "No error.";
    reference
      "RFC8355: PROBE: A Utility for Probing Interfaces";
  }

  identity EXT_ECHO_REPLY_CODE {
    base CODE;
    description
      "Subcodes for the extended echo reply ICMPv6 type.";
  }

  identity EXT_ECHO_REPLY_NO_ERROR {
    base EXT_ECHO_REPLY_CODE;
    description
      "No error.";
    reference
      "RFC8355: PROBE: A Utility for Probing Interfaces";
  }

  identity EXT_ECHO_REPLY_MALFORMED_QUERY {
    base EXT_ECHO_REPLY_CODE;
    description
      "Malformed query.";
    reference
      "RFC8355: PROBE: A Utility for Probing Interfaces";
  }

  identity EXT_ECHO_REPLY_NO_SUCH_INTERFACE {
    base EXT_ECHO_REPLY_CODE;
    description
      "No such interface.";
    reference
      "RFC8355: PROBE: A Utility for Probing Interfaces";
  }

  identity EXT_ECHO_REPLY_NO_SUCH_TABLE_ENTRY {
    base EXT_ECHO_REPLY_CODE;
    description
      "No such table entry.";
    reference
      "RFC8355: PROBE: A Utility for Probing Interfaces";
  }

  identity EXT_ECHO_REPLY_MULTIPLE_INTF_SATISFY_QUERY {
    base EXT_ECHO_REPLY_CODE;
    description
      "Multiple interfaces satisfy query.";
    reference
      "RFC8355: PROBE: A Utility for Probing Interfaces";
  }
}

module openconfig-platform-fabric {

  yang-version "1";

  // namespace
  namespace "http://openconfig.net/yang/platform/fabric";

  prefix "oc-fabric";

  import openconfig-platform { prefix oc-platform; }
  import openconfig-extensions { prefix oc-ext; }


  // meta
  organization "OpenConfig working group";

  contact
    "OpenConfig working group
    www.openconfig.net";

  description
    "This module defines data related to FABRIC components in
    the openconfig-platform model";

  oc-ext:openconfig-version "0.1.0";

  revision "2022-07-28" {
    description
      "Initial revision";
    reference "0.1.0";
  }

  // OpenConfig specific extensions for module metadata.
  oc-ext:catalog-organization "openconfig";
  oc-ext:origin "openconfig";

  // extension statements

  // feature statements

  // identity statements

  // typedef statements

  // grouping statements

  grouping fabric-config {
    description
      "Configuration data for fabric components";

    uses oc-platform:component-power-management;
  }

  // data definition statements

  // augment statements

  augment "/oc-platform:components/oc-platform:component/" +
    "oc-platform:fabric/oc-platform:config" {
    description
      "Adding fabric data to physical inventory. This subtree
      is only valid when the type of the component is FABRIC.";

    uses fabric-config;
  }

  augment "/oc-platform:components/oc-platform:component/" +
    "oc-platform:fabric/oc-platform:state" {
    description
      "Adding fabric data to physical inventory. This subtree
      is only valid when the type of the component is FABRIC.";

    uses fabric-config;
  }

  // rpc statements

  // notification statements

}

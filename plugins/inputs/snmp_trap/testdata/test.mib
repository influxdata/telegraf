SNMPv2-MIB DEFINITIONS ::= BEGIN

IMPORTS 
    NOTIFICATION-TYPE, NOTIFICATION-GROUP
        FROM test2;


snmpMIB MODULE-IDENTITY
    LAST-UPDATED "2021060900Z"
    ORGANIZATION "testing"
    CONTACT-INFO
        "EMail:  testing@emai.com"
    DESCRIPTION
        "MIB module for testing snmp_trap plugin
        for telegraf
        "
    ::={ coldStart 1 }

snmpMIBObjects OBJECT IDENTIFIER ::= { snmpMIB 1 } 

system   OBJECT IDENTIFIER ::= { sysUpTimeInstance 1 }

coldStart NOTIFICATION-TYPE
    STATUS  current
    DESCRIPTION
            "A coldStart trap signifies that the SNMP entity,
            supporting a notification originator application, is
            reinitializing itself and that its configuration may
            have been altered."
    ::= { snmpTraps 1 }

snmpBasicNotificationsGroup NOTIFICATION-GROUP
    NOTIFICATIONS { coldStart, authenticationFailure }
    STATUS        current
    DESCRIPTION
       "The basic notifications implemented by an SNMP entity
        supporting command responder applications."
    ::= { snmpMIBGroups 7 }

END
